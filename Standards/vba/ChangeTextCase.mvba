Attribute VB_Name = "frmChangeCase"
Attribute VB_Base = "0{910299D5-83ED-45DC-956C-3A1F196918F7}{0F8F9AD1-2EDC-41F8-9580-AA3CCF3F7046}"
Attribute VB_GlobalNameSpace = False
Attribute VB_Creatable = False
Attribute VB_PredeclaredId = True
Attribute VB_Exposed = False
Attribute VB_TemplateDerived = False
Attribute VB_Customizable = False

Option Explicit
'---------------------------------------------------------------------
'
'   Implementation for CHANGECASE Example
'
'  Copyright: (c) 2004 Bentley Systems, Incorporated. All rights reserved.
'
'---------------------------------------------------------------------

Private Sub cmdExit_Click()
Unload Me ' unload this form
End Sub

Private Sub cmdOK_Click()

Dim FontCase As String ' tells us if the user has selected Upper or Lower case
Dim index As Integer

CadInputQueue.SendCommand "NULL"

If optUpper.Value = True Then
    FontCase = "Upper"
ElseIf optLower.Value = True Then
    FontCase = "Lower"
Else 'user has not selected any option
  MsgBox "Please select one of the two options.", vbInformation
  Exit Sub
End If

'  Set up to read all of the text, text node, and tag elements
'  from the model
' now transform selected elements
Dim ElEnum As ElementEnumerator
' GetElementEnumerator is in the module modTextCommands
Set ElEnum = GetElementEnumerator
If ElEnum Is Nothing Then Exit Sub

While ElEnum.MoveNext
    With ElEnum.Current
        .Redraw msdDrawingModeErase
        index = index + 1
        If .Type = msdElementTypeText Then
            Dim oTextEl As TextElement
            Set oTextEl = ElEnum.Current
            
            If FontCase = "Lower" Then
                oTextEl.Text = LCase(oTextEl.Text)
            ElseIf FontCase = "Upper" Then
                oTextEl.Text = UCase(oTextEl.Text)
            End If
        ElseIf .Type = msdElementTypeTextNode Then
            Dim oTextNodeEl As TextNodeElement
            Set oTextNodeEl = ElEnum.Current
            
            oTextNodeEl.Redraw msdDrawingModeErase
            
            'change case of individual text lines
            Dim LineCount As Long
            LineCount = 1
            While (LineCount <= oTextNodeEl.TextLinesCount)
                If FontCase = "Lower" Then
                   oTextNodeEl.TextLine(LineCount) = LCase(oTextNodeEl.TextLine(LineCount))
                ElseIf FontCase = "Upper" Then
                   oTextNodeEl.TextLine(LineCount) = UCase(oTextNodeEl.TextLine(LineCount))
                End If
                LineCount = LineCount + 1
            Wend
        ElseIf .Type = msdElementTypeTag Then
            Dim oTagEl As TagElement
            Set oTagEl = ElEnum.Current
            
            If FontCase = "Lower" Then
                oTagEl.Value = LCase(oTagEl.Value)
            ElseIf FontCase = "Upper" Then
                oTagEl.Value = UCase(oTagEl.Value)
            End If
        End If
        .Redraw msdDrawingModeNormal
        .Rewrite
    End With
Wend

ShowStatus "Changed " & index & " elements."
CommandState.StartDefaultCommand

End Sub

Private Sub optUpper_Click()

End Sub

Private Sub UserForm_Click()

End Sub

Attribute VB_Name = "frmTransformText"
Attribute VB_Base = "0{1D8860C1-1E43-4CA9-AB75-C0C48F628156}{EB44A263-2B0B-48AD-BAA2-A646A8102216}"
Attribute VB_GlobalNameSpace = False
Attribute VB_Creatable = False
Attribute VB_PredeclaredId = True
Attribute VB_Exposed = False
Attribute VB_TemplateDerived = False
Attribute VB_Customizable = False

Option Explicit
'
'  Implementation for TRANSFORMTEXT Example
'
'  Copyright: (c) 2004 Bentley Systems, Incorporated. All rights reserved.
'

Private Sub chkRotate_Change()
If chkRotate.Value = False Then
    txtAngle.Value = ""
    txtAngle.Enabled = False
Else
    txtAngle.Enabled = True
End If
End Sub

Private Sub chkScale_change()
If chkScale.Value = False Then
    txtScale.Text = ""
    txtScale.Enabled = False
Else
    txtScale.Enabled = True
End If
End Sub

Private Sub cmdClear_Click()
' clear the text boxes
txtScale.Value = ""
txtAngle.Value = ""
End Sub

Private Sub cmdExit_Click()
Unload Me 'unload this form
End Sub

Private Sub cmdTransform_Click()
'used for transforming the element
Dim ScalingMatrix As Matrix3d
Dim RotationMatrix As Matrix3d
Dim TransMatrix As Matrix3d
Dim Eltrans As Transform3d

ScalingMatrix = Matrix3dIdentity
RotationMatrix = Matrix3dIdentity

If chkScale Then
    'check for non-numeric values
     If txtScale.Value = "" Or txtScale.Value = 0 Then
         MsgBox "Please enter valid numeric values only", vbInformation
         txtScale.SetFocus
         Exit Sub
     End If
     
     Dim ElScale As Double
     ElScale = txtScale.Value
    
    'set up the scaling matrix
     ScalingMatrix = Matrix3dFromScale(ElScale)
End If

If chkRotate Then
    'check for non-numeric values
    If txtAngle.Value = "" Then
        MsgBox "Please enter valid numeric values only", vbInformation
        txtAngle.SetFocus
        Exit Sub
    End If

    Dim Angle As Double
    Angle = Radians(txtAngle.Value)  'retrieve values from user and change to radians

    RotationMatrix = Matrix3dFromAxisAndRotationAngle(2, Angle)
End If

'  Now combined the transformations
TransMatrix = Matrix3dFromMatrix3dTimesMatrix3d(ScalingMatrix, RotationMatrix)

' now transform selected elements
Dim oElEnum As ElementEnumerator

' GetElementEnumerator is in the module modTextCommands
Set oElEnum = GetElementEnumerator
If oElEnum Is Nothing Then Exit Sub

While oElEnum.MoveNext
   'check to see if selected element is a Text element
    If (oElEnum.Current.Type <> msdElementTypeText) Then
        MsgBox "Please select TextElements only", vbInformation
        Exit Sub
    End If

    Dim oEl As TextElement ' create an element object
    Set oEl = oElEnum.Current 'copy the current element
    
    oEl.Redraw msdDrawingModeErase
    
    Eltrans = Transform3dFromMatrix3dAndFixedPoint3d(TransMatrix, oEl.Origin)
    oEl.Transform Eltrans

    oEl.Rewrite
    oEl.Redraw
Wend

ShowPrompt "Done"
End Sub

Private Sub UserForm_Click()

End Sub

Attribute VB_Name = "modTextCommands"
'
'  Copyright: (c) 2004 Bentley Systems, Incorporated. All rights reserved.
'
Option Explicit
'  The ChangeCase and TransformText commands both use this to get an
'  ElementEnumerator to retrieve the list of elements to process.
Function GetElementEnumerator() As ElementEnumerator
    If ActiveModelReference.AnyElementsSelected Then
        Set GetElementEnumerator = ActiveModelReference.GetSelectedElements ' get the selected elements
    ElseIf ActiveDesignFile.Fence.IsDefined Then
        Set GetElementEnumerator = ActiveDesignFile.Fence.GetContents
    Else
        If MsgBox("No fence or selection set defined. Process all elements?", vbOKCancel) = vbCancel Then
            Exit Function
        End If
        Dim sc As New ElementScanCriteria
        sc.ExcludeAllTypes
        sc.IncludeType msdElementTypeText
        sc.IncludeType msdElementTypeTextNode
        Set GetElementEnumerator = ActiveModelReference.Scan(sc)
    End If
End Function
Sub ChangeCase()
    frmChangeCase.Show
End Sub
